' Reset all to #304

' Check if this file is a drawing
If Not TypeOf (ThisApplication.ActiveDocument) Is DrawingDocument Then
    MessageBox.Show("Drawing not active!")
    Exit Sub
End If

'Set the find and replace text
Dim findTXT As String = "430"
Dim replaceTXT As String = "304"

Dim searchs() As String = {"20GSS", "20 GSS", "20G.S.S", "20 G.S.S", "20gss", "20 gss", "20g.s.s", "20 g.s.s"}

Dim oDoc As DrawingDocument = ThisDoc.Document
Dim oSheets As Sheets = oDoc.Sheets

''' Loop through all sheets and all notes and print the text to the logger
For Each oSheet As Sheet In oSheets
    For Each iNote As DrawingNote In oSheet.DrawingNotes.GeneralNotes

        Dim iText As String = iNote.FormattedText
        Dim oText As String = ""

        For Each search As String In searchs
            If iText.Contains(search) And iText.Contains("#" & findTXT) Then
                oText = Replace(iText, findTXT, replaceTXT)
                Exit For
            ElseIf iText.Contains(search) And iText.Contains(findTXT) Then
                oText = Replace(iText, findTXT, "#" & replaceTXT)
                Exit For
            ElseIf iText.Contains(search) And Not iText.Contains(replaceTXT) Then
                oText = Replace(iText, search, search & "#" & replaceTXT)
                Exit For
            End If
        Next

        'Logger.Info("change?: " & oText)
        If Not String.IsNullOrEmpty(oText) Then iNote.FormattedText = oText
    Next
Next

' Add a note to the first sheet
Dim frontPage As Sheet = oSheets.Item(1)

Dim insertPoint = ThisApplication.TransientGeometry.CreatePoint2d(2, 3)

Dim frontTXT As String = "20 G.S.S all #304"
Dim frontNote As String = "<StyleOverride FontSize='0.6096'>" & frontTXT & "</StyleOverride>"
frontPage.DrawingNotes.GeneralNotes.AddFitted(insertPoint, frontNote)

MsgBox("All reset to #" & replaceTXT)
