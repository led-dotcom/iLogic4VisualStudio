'Path to the Excel file
Dim excelPath As String = "Query.xlsx"
Dim sheetName As String = "Sheet1"

'Find last 5 projects
MultiValue.List("Project") = GoExcel.CellValues(excelPath, sheetName, "A2", "A6")

MessageBox.Show("New projects updated!", "Success")
