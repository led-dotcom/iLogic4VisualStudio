' Check if this file is a drawing
If Not TypeOf (ThisApplication.ActiveDocument) Is DrawingDocument Then
MessageBox.Show("Drawing not active!")
Exit Sub
End If

'Path to the Excel file
Dim excelPath As String = "J:\Reference\Project sync to Airtalbe.xlsx"
Dim sheetName As String = "Projects"

' Creation of a custom/user parameter "Project" 
Dim oDoc As DrawingDocument = ThisDoc.Document
Dim oUserParameters As UserParameters = oDoc.Parameters.UserParameters
'Dim oTextParam As UserParameter = oUserParameters.AddByValue("Project", "", kTextUnits)

Try
Dim p As String = Parameter("Project")
Catch
Dim oTextParam As UserParameter = oUserParameters.AddByValue("Project", "", UnitsTypeEnum.kTextUnits)
End Try

'Find last 100 projects
MultiValue.List("Project") = GoExcel.CellValues(excelPath, sheetName, "C2", "C101")

'MultiValue.SetList("Project", GoExcel.CellValues(excelPath, sheetName, "C2", "C11"))

MessageBox.Show("New projects updated!", "Success")



'' This subroutine creates a text user parameter in the active part document.
'Public Sub CreateTextUserParameter()
'Dim oDoc As DrawingDocument = ThisDoc.Document

'Dim oUserParameters As UserParameters = oDoc.Parameters.UserParameters

'Dim oTextParam As UserParameter = oUserParameters.AddByValue("Project", "", kTextUnits)
'End Sub

'Public Sub CreateParameters()
'    ' Get the active document.  Assumes a part document is active.
'    Dim partDoc As PartDocument
'    Set partDoc = ThisApplication.ActiveDocument

'    ' Get the UserParameters collection
'    Dim userParams As UserParameters
'    Set userParams = partDoc.ComponentDefinition.Parameters.UserParameters

'    ' Create a parameter using an expression.  The parameters unit is specified
'    ' as millimeters, but the value of the parameter will be 3 inches because
'    ' the unit is specified as part of the expression.
'    Dim param As Parameter
'    Set param = userParams.AddByExpression("NewParam1", "3 in", kMillimeterLengthUnits)

'    ' Create a parameter using a value.  When setting by value, the value is always
'    ' in database units.  In this case it is a length so it will always be in
'    ' centimeters.  The units used for the parameter will be the current length units
'    ' of the document because it's defined to use the default display length units.
'    Set param = userParams.AddByValue("NewParam2", 3 * 2.54, kDefaultDisplayLengthUnits)
'End Sub
